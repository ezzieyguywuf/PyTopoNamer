import FreeCAD
import Part

# add PyTopoNamer to path and import
import sys
path = 'path/to/PyTopoNamer'
sys.path.append(path)
from PyTopoNamer.TopoNamer import TopoNamer

TARGET_EDGE = 9

def runExample():
    # We'll use this class to manage our various Part objects
    tester = MyTester()

    # Make a 10x10x0 cube and fuse with a r=2.5,h=10.0 cylinder
    fuse1 = tester.makeFuse()

    # This is similar to how FreeCAD currently does Chamfers. You provide a Base shape, and an
    # Edge Number, and it does the rest
    chamf1 = tester.makeFreeCADChamf(fuse1.Shape, TARGET_EDGE)
    # make a copy
    chamf1a = tester.makeFreeCADChamf(fuse1.Shape, TARGET_EDGE)

    # In the FreeCAD implementation, when the underlying Base shape changes, the Chamfer is
    # recomputed using the same Edge Number. This is why the chamfer moves
    fuse1.makeCylHeight5mm()
    # This is akin to the recompute method in FreeCAD
    chamf1.changeBase(fuse1.Shape)

    # Now let's try again with the TopoNamer prototype
    fuse2 = tester.makeFuse()

    # We'll need to ask the fuse2 object about the name of the Edge which we intend to chamfer
    # before we build the Chamfer object. In real life, rather using a hard coded value
    # (TARGET_EDGE in this example) the user would some how select an Edge
    edgeName = fuse2.getEdgeName(TARGET_EDGE)

    # Now we can build our Chamfer. Notice that our Chamfer object only cares about the
    # edgeName that TopoNamer provided - it does NOT care about TARGET_EDGE (the actual
    # edge index)
    chamf2 = tester.makeTopoNamerChamf(fuse2, edgeName)
    # make a copy
    chamf2a = tester.makeTopoNamerChamf(fuse2, edgeName)

    # Now, when our base shape changes, our Chamfer construction algorithm should still be
    # able to find the same edge to Chamfer
    fuse2.makeCylHeight5mm()
    # this is akin the the FreeCAD recompute method
    chamf2.changeBase(fuse2)

    # Finally, let's display all the objects so we can get a visual
    tester.addFeature(chamf1a, 'Chamfer', (0,0), (1.0, 0.0, 0.0))   # FreeCAD original chamfer
    tester.addFeature(chamf1, 'Chamfer', (0,20), (1.0, 0.0, 0.0))   # FreeCAD re-constructed chamfer
    tester.addFeature(fuse1, 'Fusion', (0,40), (1.0, 0.0, 0.0))     # The re-constructed Fuse (base shape)
    tester.addFeature(chamf2a, 'Chamfer', (20,0), (0.0, 0.0, 1.0))  # TopoNamer original chamfer
    tester.addFeature(chamf2, 'Chamfer', (20,20), (0.0, 0.0, 1.0))  # TopoNamer re-constructed chamfer 
    tester.addFeature(fuse2, 'Fusion', (20,40), (0.0, 0.0, 1.0))    # The re-constructed Fuse (base shape)
    Gui.activeDocument().activeView().viewAxonometric()
    Gui.SendMsgToActiveView('ViewFit')

class MyDoc(object):
    '''This is just a shell class b/c PyTopoNamer expects a FreeCAD Part::Feature, not a
    pure Shape object'''
    def __init__(self, Shape):
        self.Shape = Shape

class MyFuse(object):
    '''This class is intended to mock the FreeCAD Part::Fusion class'''
    def __init__(self):
        '''note: really we should take a list of shapes, but for the purposes of this
        example we\'ll just explicitly make the two shapes'''
        self._box = Part.makeBox(10.0, 10.0, 10.0)
        self._cyl = Part.makeCylinder(2.5, 10.0)
        self.Shape = self._box.fuse(self._cyl)

        self._namer = TopoNamer()

        docObject = MyDoc(self.Shape)
        self._namer.addShape(docObject)

    def makeCylHeight5mm(self):
        '''Note: The key here is knowing which faces from the original Fused shape have
        been modified into a new OCC Face.'''
        self._cyl = Part.makeCylinder(2.5, 5.0)
        origFaces = self.Shape.Faces[:]
        self.Shape = self._box.fuse(self._cyl, withHistory=True)
        # Use Jnxd's history framework!!!
        history   = self.Shape.History
        newFaces  = self.Shape.Faces[:]

        modifiedFaces = []
        deletedFaces  = []
        newFaces      = []

        for tracker in self._namer._tracker._faceTrackers:
            oldFace  = tracker.getOCCFace()
            modFaces = history.modified(oldFace)
            nueFaces = history.generated(oldFace)
            if history.isDeleted(oldFace):
                deletedFaces.append(oldFace)
                continue
            for i,modFace in enumerate(modFaces):
                # only the first will be considered modified. Any others will be
                # considered new
                if i == 0:
                    # make sure this modFace wasn't already added
                    check = [i[1].isEqual(modFace)==False for i in modifiedFaces]
                    if all(check):
                        modifiedFaces.append([oldFace, modFace])
                else:
                    # make sure this newFace wasn't already added
                    check = [i.isEqual(modFace)==False for i in nueFaces]
                    if all(check):
                        newFaces.append(modFace)
            for newFace in nueFaces:
                # make sure this newFace wasn't already added
                check = [i.isEqual(newFace)==False for i in newFaces]
                if all(check):
                    newFaces.append(newFace)

        self._namer.modifyShape(modifiedFaces=modifiedFaces, deletedFaces=deletedFaces)

    def getEdgeName(self, edgeNum):
        '''an access method for the TopoNamer'''
        edge = self.Shape.Edges[edgeNum]
        return self._namer.getEdgeName(edge)

    def getEdge(self, edgeName):
        '''an access method for the TopoNamer'''
        targetEdge = self._namer.getEdgeByName(edgeName)[0]
        return targetEdge

class MyFreeCADChamfer(object):
    '''This class is intended to mock the FreeCAD Part::Chamfer class. Notice how the
    _construct method is hamstringed by always relying on the same position of the target
    Edge within the Base Shape\'s Edges list.'''

    def __init__(self, base, edgeNum):
        '''Note: FreeCAD relies on finding the Edge by Index'''
        self._base = base
        self._edgeNum = edgeNum
        self._construct()

    def _construct(self):
        # we always get the `self._edgeNum` Edge, no matter what
        chamfEdge = self._base.Edges[self._edgeNum]
        self.Shape = self._base.makeChamfer(1.0, [chamfEdge])
        App.ActiveDocument.recompute()

    def changeBase(self, newBase):
        self._base = newBase
        self._construct()

class MyTopoNamerChamf(object):
    '''This class is intended to show how a Chamfer can be consistently applied to the
    same Edge regardless of how the underlying Base Shape changes. Notice how rather than
    relying on the position of our target Edge in our Base Shape\'s Edges list, we rely on
    the Base Shape itself to give us the actual OCC Edge. All we need is to keep track of
    the EdgeName that TopoNamer creates'''

    def __init__(self, base, edgeName):
        self._base = base
        self._edgeName = edgeName
        self._construct()

    def _construct(self):
        # Notice how, unlike the FreeCAD solution, we don't have to rely on the edge's
        # index within the base shape's Edges list. Instead, we ask the base shape to
        # provide us with the Edge that we're interested in - we reference this Edge by
        # the edgeName that TopoNamer created
        targetEdge = self._base.getEdge(self._edgeName)
        baseShape = self._base.Shape
        self.Shape = baseShape.makeChamfer(1.0, [targetEdge])

    def changeBase(self, newBase):
        '''Even though the Base changes, it should still be able to give us the proper
        Edge to chamfer.
        
        Note: in this simple example, we don\'t bother about validating that the newBase
        is some sort of descendent of the original Base. In other words, we assume that
        the newBase._namer holds information from the original Base._namer'''
        self._base = newBase
        self._construct()


class MyTester(object):
    '''This class is just a helper. It reduces redundant code in this Macro'''
    def __init__(self):
        self._appName = '__chamfTest'

        for docName in App.listDocuments().keys():
            if docName == self._appName:
                App.closeDocument(docName)

        self._app = App.newDocument(self._appName)
        App.setActiveDocument(self._appName)
        Gui.ActiveDocument = Gui.getDocument(self._appName)

        self.namer = TopoNamer()

    def makeFuse(self):
        fuse = MyFuse()
        return fuse

    def makeFreeCADChamf(self, base, edgeNum):
        chamf = MyFreeCADChamfer(base, edgeNum)
        return chamf

    def makeTopoNamerChamf(self, base, edgeName):
        '''note: this method relies on the `base` managing an instance of TopoNamer'''
        chamf = MyTopoNamerChamf(base, edgeName)
        return chamf

    def addFeature(self, shape, name, xy, color):
        feat = self._app.addObject('Part::Feature', name)
        feat.Shape = shape.Shape
        feat.Placement = App.Placement(App.Vector(xy[0],xy[1],0),App.Rotation(App.Vector(0,0,1),0))
        vo = Gui.ActiveDocument.getObject(feat.Name)
        vo.ShapeColor = color
        return feat

runExample()
